Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
'      VBA Sample
'
'      Copyright (C) 1996, 1997, 1998, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
Option Explicit

Const USER_ALL = "<All Users>"
Const TAG_APPLICATION_NAME = "ObjectTracker"
Const TAG_DICTIONARY_NAME = "ObjectTrackerDictionary"
Const TAG_XRECORD_NAME = "ObjectTrackerXRecord"
Const TAG_USER = "User: "
Const TAG_TIME = "Time: "
Const TAG_SEPERATOR = "_______________________________"
Const TAG_OPERATION = "Operation: "
Const NOT_LOGGEDIN = "<User Not Logged In>"
Const OPERATION_MODIFIED = "Modified Object"
Const NEW_DATA_ELEMENTS = 6 ' How many pieces of new data are we going to
                            ' add when we update the object


' Used to track changes to ThisDrawing
Const THISDRAWING_ID = "999999"

' Const new data array positions
Const ELEMENT_APPNAME = 0
Const ELEMENT_OBJECTID = 1
Const ELEMENT_USERNAME = 2
Const ELEMENT_TIME = 3
Const ELEMENT_OPERATION = 4
Const ELEMENT_SEPERATOR = 5

' A time value used to determine the command name for a particular modified action
Const MAXIMUM_TIME_ELAPSED = 20     ' Milliseconds

' Unique identifiers to distinguish our XRecordData
Const TYPE_STRING = 1

Private RecordTime As Double
Private SelectedObjectID As Variant
Private NewXRecordData() As Variant, NewXRecordDataType() As Integer
Private CurrentXRecordData As Variant, CurrentXRecordDataType As Variant
Private SelectedXRecordDataTypes As Variant, SelectedXRecordDataValues As Variant
Private SelectedXRecordDataArraySize As Long

Public TrackingDictionary As AcadDictionary
Public TrackingXRecord As AcadXRecord
Public RanCorrectly As Boolean

Public Sub Run_Sample()
    ' This is a simple viewer that allows the user to select an object
    ' and see the associated XRecordData that we have been saving
    '
    ' This will only display information we added which is stored as
    ' XRecordData type 1 (String)
    
    Dim SourceObject As Object, Point As Variant
    Dim sMessage As String
    Dim iCount As Long
    Dim DataType As Integer, Data As String
    Dim AppName As String
        
        
    RanCorrectly = True
    
    SelectedXRecordDataArraySize = 0
    
    ' First attach to our tracking dictionary and XRecord
    On Error GoTo NoTrackingDictionary
    Set TrackingDictionary = ThisDrawing.Dictionaries(TAG_DICTIONARY_NAME)
    Set TrackingXRecord = TrackingDictionary.GetObject(TAG_XRECORD_NAME)
    
    ' Get the object for which to display information
    On Error Resume Next
    ThisDrawing.Utility.GetEntity SourceObject, Point, "Select an object to view tracking information..."
    If Err.Number = 0 Then
        SelectedObjectID = SourceObject.objectID
    Else
        SelectedObjectID = THISDRAWING_ID
    End If
    On Error GoTo ErrorTrap
    
    ' Get the XRecordData for the select object
    TrackingXRecord.GetXRecordData SelectedXRecordDataTypes, SelectedXRecordDataValues
    
    ' Get the number of XRecordData elements
    On Error GoTo NoXRecordData
    SelectedXRecordDataArraySize = UBound(SelectedXRecordDataTypes)
    
    ' Clear old user list
    UserForm1.ComboUserList.Clear
    
    ' Add list of users from XRecordData; start by adding a
    ' placeholder representing all users
    AddUser USER_ALL
    For iCount = 0 To SelectedXRecordDataArraySize
        ' Get information for this element
        DataType = SelectedXRecordDataTypes(iCount)
        Data = SelectedXRecordDataValues(iCount)
        
        If DataType = TYPE_STRING Then
            If Left(Data, Len(TAG_USER)) = TAG_USER Then
                AddUser CStr(Data)
            End If
        End If
    Next
    
    ' Select first user
    UserForm1.ComboUserList.ListIndex = 0

    UserForm1.Show
    
FINISH:
    Exit Sub
    
NoTrackingDictionary:
    MsgBox "No tracking information is available for this drawing.", vbExclamation
    Exit Sub

ErrorTrap:
    MsgBox "The following error occurred: " & Err.Description, vbExclamation
    Exit Sub

NoXRecordData:
    MsgBox "The selected object does not contain XRecordData.", vbInformation
    Exit Sub
End Sub

Private Sub AcadDocument_EndCommand(ByVal CommandName As String)
    Dim object As Object
    Dim TimeDiff As Double
    Dim RecordIndex As Long
    
    TimeDiff = Timer - RecordTime
    
    '----------------------------------------
    ' Make sure we have access to our XRecord
    '----------------------------------------
    ConnectToXRecord
    
    ' See if we are within the maximum elapsed time allowed. If so, append command to
    ' the last object modified. Otherwise, consider this a new operation and record
    If TimeDiff < MAXIMUM_TIME_ELAPSED Then
         ' Get correct record array element index
        TrackingXRecord.GetXRecordData CurrentXRecordDataType, CurrentXRecordData
        RecordIndex = ELEMENT_OPERATION
         
        ' If this operation is a modify, then append the command used to modifiy the object
        CurrentXRecordData(RecordIndex) = CurrentXRecordData(RecordIndex) & " (" & CommandName & ")"    ' Add command name
                 
        ' Write data to object
        TrackingXRecord.SetXRecordData CurrentXRecordDataType, CurrentXRecordData
    Else
        ' Record operations that appear not to be associated with any object
        RecordOperation THISDRAWING_ID, "FINISHED COMMAND: " & CommandName
    End If
    
    ' Reset XRecord array variables
    ReDim NewXRecordData(0): ReDim NewXRecordDataType(0)
    CurrentXRecordData = Empty: CurrentXRecordDataType = Empty
    
    ' Reset time
    RecordTime = 0
End Sub

Public Sub AcadDocument_ObjectModified(ByVal object As Object)
    ' Intercept and record when an object is modified
    
    
    If (object.ObjectName <> "AcDbBlockTableRecord") And _
       (object.ObjectName <> "AcDbXrecord") And _
       (object.ObjectName <> "AcDbDictionary") Then

        RecordOperation object.objectID, OPERATION_MODIFIED
    End If
    
End Sub

Private Sub ConnectToXRecord()
    If TrackingDictionary Is Nothing Then  ' Make sure we have our tracking object
        On Error GoTo CreateDictionary
        Set TrackingDictionary = ThisDrawing.Dictionaries(TAG_DICTIONARY_NAME)
    End If
    
    If TrackingXRecord Is Nothing Then
        On Error GoTo CreateXRecord
        Set TrackingXRecord = TrackingDictionary.GetObject(TAG_XRECORD_NAME)
    End If

    Exit Sub
    
CreateDictionary:
    ThisDrawing.Dictionaries.Add TAG_DICTIONARY_NAME
    Resume

CreateXRecord:
    TrackingDictionary.AddXRecord TAG_XRECORD_NAME
    Resume
End Sub

Private Sub RecordOperation(ByVal objectID As Long, ByRef Operation As String)
    Dim sysVarName As String
    Dim sysVarData As Variant
    
    '----------------------------------------
    ' Make sure we have access to our XRecord
    '----------------------------------------
    ConnectToXRecord
    
    '----------------------------------------
    ' Get general information
    '----------------------------------------
    sysVarName = "LOGINNAME"
    sysVarData = ThisDrawing.GetVariable(sysVarName)

    ' For this example, we use a general message if the user is not logged in,
    ' but a developer could add information such as the current machine or profile name
    '
    ' If we didn't get a user name, make that fact apparent
    If (Trim(sysVarData) = "") Or (sysVarData = Empty) Then
        sysVarData = NOT_LOGGEDIN
    End If

    '----------------------------------------
    ' Add new information to object
    '----------------------------------------
    ' The first XRecordData pair must be a unique identifier so it is not overwritten
    ReDim NewXRecordDataType(0 To NEW_DATA_ELEMENTS - 1)
    ReDim NewXRecordData(0 To NEW_DATA_ELEMENTS - 1)
    NewXRecordDataType(ELEMENT_APPNAME) = TYPE_STRING: NewXRecordData(ELEMENT_APPNAME) = TAG_APPLICATION_NAME
    NewXRecordDataType(ELEMENT_OBJECTID) = TYPE_STRING: NewXRecordData(ELEMENT_OBJECTID) = objectID                   ' Current Object
    NewXRecordDataType(ELEMENT_USERNAME) = TYPE_STRING: NewXRecordData(ELEMENT_USERNAME) = TAG_USER & sysVarData      ' Add current user name
    NewXRecordDataType(ELEMENT_TIME) = TYPE_STRING: NewXRecordData(ELEMENT_TIME) = TAG_TIME & Now             ' Add current day and time
    NewXRecordDataType(ELEMENT_OPERATION) = TYPE_STRING: NewXRecordData(ELEMENT_OPERATION) = TAG_OPERATION & Operation  ' Add operation performed
    NewXRecordDataType(ELEMENT_SEPERATOR) = TYPE_STRING: NewXRecordData(ELEMENT_SEPERATOR) = TAG_SEPERATOR              ' Add data seperator

     ' Save existing XRecordData for this object and append the new data
     TrackingXRecord.GetXRecordData CurrentXRecordDataType, CurrentXRecordData
     CreateNewXRecordData CurrentXRecordDataType, CurrentXRecordData, NewXRecordDataType, NewXRecordData

    ' Write data to object
    TrackingXRecord.SetXRecordData NewXRecordDataType, NewXRecordData
             
    ' Reset XRecord array variables
    ReDim NewXRecordData(0): ReDim NewXRecordDataType(0)
    CurrentXRecordData = Empty: CurrentXRecordDataType = Empty
    
    ' This allows us to compare the time in the EndCommand event. If the times are within a
    ' difference range we will record the action performed on this object.
    RecordTime = Timer
End Sub

Private Sub CreateNewXRecordData(SourceArray1 As Variant, SourceArray2 As Variant, DestinationArray1 As Variant, DestinationArray2 As Variant)
    Dim SourceArrayStart As Long, SourceArrayFinish As Long
    Dim NewArraySize As Long
    Dim iCount As Long
    Dim SourceType As Integer, SourceData As Variant, SourceArraySize As Long
    
    ' Get current number of XRecordData elements. We'll just use the Type array
    ' since both the XRecordData Types and XRecordData Data arrays should be the same size
    On Error GoTo No_XRecordData
    SourceArrayStart = LBound(SourceArray1)
    SourceArrayFinish = UBound(SourceArray1)
    SourceArraySize = (SourceArrayFinish - SourceArrayStart) + 1
    On Error GoTo 0
    
    NewArraySize = SourceArraySize + NEW_DATA_ELEMENTS
    
    ' Create our new XRecordData structure as large enough to handle the
    ' old information, plus the new information we will add
    ReDim Preserve DestinationArray1(0 To NewArraySize - 1)
    ReDim Preserve DestinationArray2(0 To NewArraySize - 1)
    
    ' Transfer old data to new array
    ' Transfer information in reverse order so we see the latest data first
    '
    ' Note - We've already placed the new data at the top of this array
    For iCount = SourceArrayStart To SourceArrayFinish
        SourceType = SourceArray1(iCount)
        SourceData = SourceArray2(iCount)
        
        DestinationArray1(NEW_DATA_ELEMENTS + iCount) = SourceType     ' Shuffle data back one since we're loosing the old ApplicationName
        DestinationArray2(NEW_DATA_ELEMENTS + iCount) = SourceData     ' Shuffle data back one since we're loosing the old ApplicationName
    Next
    
    Exit Sub
    
No_XRecordData:

End Sub

Private Sub AddUser(ByVal sUserName As String)
    Dim iCount As Integer, iListedCount As Integer
    
    iListedCount = UserForm1.ComboUserList.ListCount - 1    ' Start at zero index
    sUserName = UCase(sUserName)                            ' Make sure it is not case sensitive
    
    ' Add names to the list of available users
    If iListedCount = 0 Then
        ' If we don't have any names listed, then add this name
        UserForm1.ComboUserList.AddItem sUserName
    Else
        ' Search the list of added names, if we don't find this name, then add
        For iCount = 0 To iListedCount
            If UserForm1.ComboUserList.List(iCount) = sUserName Then GoTo FINISH
        Next
        UserForm1.ComboUserList.AddItem sUserName
    End If
    
FINISH:
End Sub

Public Sub DisplayXRecordDataForUser(ByVal sUserName As String)
    Dim RecordCount As Long, ElementCount As Long, TotalRecords  As Long
    Dim DataType As Integer
    Dim Data As String
    Dim CorrectUser As Boolean
    
    TotalRecords = ((SelectedXRecordDataArraySize + 1) / NEW_DATA_ELEMENTS)
    
    ' Display XRecordData for a particular user
    For RecordCount = 0 To (TotalRecords - 1)
        ' Do we have the correct object?
        Data = SelectedXRecordDataValues((RecordCount * NEW_DATA_ELEMENTS) + ELEMENT_OBJECTID)
        If SelectedObjectID <> Data Then GoTo SKIP_RECORD
            
        ' Do we have the correct user?
        Data = SelectedXRecordDataValues((RecordCount * NEW_DATA_ELEMENTS) + ELEMENT_USERNAME)
        If Left(Data, Len(TAG_USER)) = TAG_USER Then
            CorrectUser = (StrComp(Data, sUserName, vbTextCompare) = 0)
            ' If we want to display all users, then do not filter
            If (StrComp(sUserName, USER_ALL, vbTextCompare) = 0) Then CorrectUser = True
        End If
                
        ' Display data for this user
        If CorrectUser Then
            Data = SelectedXRecordDataValues((RecordCount * NEW_DATA_ELEMENTS) + ELEMENT_USERNAME)
            UserForm1.TextTrackedInformation.Text = UserForm1.TextTrackedInformation.Text & Data & vbCrLf
            
            Data = SelectedXRecordDataValues((RecordCount * NEW_DATA_ELEMENTS) + ELEMENT_TIME)
            UserForm1.TextTrackedInformation.Text = UserForm1.TextTrackedInformation.Text & Data & vbCrLf
            
            Data = SelectedXRecordDataValues((RecordCount * NEW_DATA_ELEMENTS) + ELEMENT_OPERATION)
            UserForm1.TextTrackedInformation.Text = UserForm1.TextTrackedInformation.Text & Data & vbCrLf
            
            Data = SelectedXRecordDataValues((RecordCount * NEW_DATA_ELEMENTS) + ELEMENT_SEPERATOR)
            UserForm1.TextTrackedInformation.Text = UserForm1.TextTrackedInformation.Text & Data & vbCrLf
        End If

SKIP_RECORD:
    Next
End Sub

Attribute VB_Name = "UserForm1"
Attribute VB_Base = "0{909523C6-1413-4ADE-916F-7EE26B9C5099}{075A3F1D-27B6-41B4-9A3D-E69D13C1FBC2}"
Attribute VB_GlobalNameSpace = False
Attribute VB_Creatable = False
Attribute VB_PredeclaredId = True
Attribute VB_Exposed = False
Attribute VB_TemplateDerived = False
Attribute VB_Customizable = False
'      VBA Sample
'
'      Copyright (C) 1996, 1997, 1998, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Option Explicit

Private Sub ButtonClose_Click()
    UserForm1.Hide
End Sub

Private Sub ButtonRefresh_Click()
    UserForm1.TextTrackedInformation.Text = ""    ' Clear textbox
    ThisDrawing.DisplayXRecordDataForUser UserForm1.ComboUserList.Text
End Sub

Private Sub ComboUserList_Change()
    UserForm1.TextTrackedInformation.Text = ""    ' Clear textbox
    ThisDrawing.DisplayXRecordDataForUser UserForm1.ComboUserList.Text
End Sub


Private Sub UserForm_Initialize()
    If Not (ThisDrawing.RanCorrectly) Then
        MsgBox "You must start by running the macro: Run_Sample", vbExclamation
        End
    End If
End Sub
